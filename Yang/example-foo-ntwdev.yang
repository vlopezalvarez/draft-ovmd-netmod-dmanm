module foo-ntwdev {
  namespace "urn:example:foo-ntwdev";
  prefix "netdevfoo";

  import foo {
    prefix "foo";
  }

  organization "Example Organization";
  contact "example@example.com";
  description "YANG model for foo-dev.";

  revision "2024-07-05" {
    description
      "Initial version.";
    reference
      "RFC XXXX: YANG Model for foo-dev";
  }

  leaf foo {
    type leafref {
      path "/foo:foo";
    }
    description
      "Reference to foo leaf from foo.yang";
  }

  container deployment {
    description
      "Deployment container.";

    list ntw-element {
      key "ne-id";
      description
        "List of network elements.";

      leaf ne-id {
        type string;
        description
          "Network element identifier.";
      }
      leaf devmod-alias {
        type string;
        description
          "Device module alias for the deployment.";
      }
    }

    list grp-ntw-elements {
      key "grp-ne-id";
      description
        "List of group of network elements.";

      leaf grp-ne-id {
        type string;
        description
          "Group of network element identifier.";
      }
      leaf devmod-alias {
        type string;
        description
          "Device module alias for the deployment.";
      }
    }
  }
}
