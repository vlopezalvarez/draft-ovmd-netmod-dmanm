module ietf-grp-ntw-elements {
  yang-version 1.1;
  namespace "urn:ietf:params:xml:ns:yang:ietf-grp-ntw-elements";
  prefix "grp";

  organization
    "IETF NETMOD Working Group";
  contact
    "WG Web:  <https://datatracker.ietf.org/wg/netmod/>
    WG List:  <mailto:netmod@ietf.org>

    Editor:   Oscar Gonzalez de Dios
              <mailto:oscar.gonzalezdedios@telefonica.com>
    Editor:   Victor Lopez
              <mailto:victor.lopez@nokia.com>
    Editor:   Mohamed Boucadair
              <mailto:mohamed.boucadair@orange.com>
    Editor:   Daniele Ceccarelli
              <mailto:dceccare@cisco.com>";

  description
    "YANG model for group of network elements.";

  revision "2024-07-05" {
    description "Initial version.";
    reference
      "RFC XXXX: An Approach to Expose 'Device Models'
      -as-'Network Models'";
  }

  list grp-ntw-elements {
    key "grp-ne-id";
    description
      "List of groups of network elements.";

    leaf grp-ne-id {
      type string;
      description
        "Group of network element identifier.";
    }

    list ntw-element {
      key "ne-id";
      description
        "List of network elements.";

      leaf ne-id {
        type string;
        description
          "Network element identifier.";
      }
    }
  }
}
